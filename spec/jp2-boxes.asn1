-- jp2-boxes.asn1
--
-- JP2 / JPX file structure (ITU-T T.800 Annex I, T.801 Annex M): the box
-- tree, with the boxes esajpip interprets and the JP2 header boxes (T.800
-- I.5.3) modeled in full, and everything else opaque. Together with
-- j2k-codestream.asn1 this makes a generated vector a complete .jp2 or .jpx
-- file.
--
-- Design (encodings in jp2-boxes.acn):
--   * LBox is an ACN-inserted determinant with mapping function `lbox`
--     (wire = payload bytes + 8). TBox is an ACN-inserted determinant of
--     type BoxType, named after its box (topType in TopBox, innerType in
--     InnerBox, resType in ResBox, jp2Type, profileTopType and
--     profileInnerType in the profile boxes); it selects the payload
--     through an ACN parameter.
--   * A superbox's children are a `SEQUENCE OF` with `size deduced` inside
--     the CONTAINING region of the superbox -- the nested-container case the
--     deduced-size specification was written for.
--   * asn1scc forbids recursive types, so nesting is two levels: TopBox
--     (may be a superbox) contains InnerBox, whose superbox alternatives
--     (jpch, ftbl, dtbl, asoc, and jp2h and jplh) are opaque. This covers
--     the children of jp2h/jpch/jplh/ftbl/dtbl/uinf and of a top-level
--     asoc in the standard model. A jpch, ftbl or dtbl below the top level
--     decodes, and hv_rule_child names its placement (box.nested-top-level);
--     a nested asoc decodes, as the server preserves asoc contents without
--     interpreting them. A box type with no alternative at its level (flst
--     or url at the top level, which ReadJPX rejects) fails to decode. The
--     other boxes that belong inside another (a header box, nlst, lbl) are
--     opaque at the top level, as ReadJPX skips them. Two third levels are
--     modeled, each with children of a type of their own: the Resolution
--     box (res, in jp2h or jplh; ResBox) and the Colour Group box (cgrp, in
--     jplh; CgrpBox). At the top level a cgrp is opaque, so that a rule
--     names its placement.
--   * Below the levels the types reach, and in the boxes they keep opaque,
--     the box tree rules (hv_rule_box_tree, ../jpeg2000/hv_rules.c) read the
--     file's bytes: every box to HV_BOX_DEPTH_MAX levels in every superbox
--     of the file's kind, where the placement and count rules at the end
--     apply, and the contents of the UUID Info, UUID List, UUID, Data Entry
--     URL (in a uinf), Label and Cross-Reference boxes, read one element at
--     a time with the types below (UuidCount, UuidId, CrefType).
--   * A file whose ftyp brand is 'jpx ' is a JPX file (Jp2Family), any
--     other a JP2 file (Jp2File: T.800's boxes only, T.801's opaque), as
--     T.801 M.11.7.2 tells them apart; a JPX file that lists 'jp2 ' is
--     checked as a JP2 file too.
--   * jp2c carries a full Codestream (CONTAINING), so a JP2 vector exercises
--     the codestream framing and the marker bodies in one file.
--
-- Not modeled (documented gaps; the server accepts XLBox and LBox = 0):
--   * XLBox (LBox = 1, 64-bit length): the payload would need one of two
--     determinants depending on LBox; never required under the INT_MAX
--     file limit.
--   * LBox = 0 (box extends to end of file): a region cannot be both
--     determinant-sized and deduced.
--   * Codestream Header boxes inside a Compositing Layer Extensions box, and
--     codestreams inside a Multiple Codestream box, are outside the types;
--     every jpch, jp2c and ftbl they read is top level, as the server
--     requires. The box tree rules place them, and the count of
--     codestreams against headers leaves a file with a j2cx or jclx out.
--   * ICC profiles (colr METH 2, 3) are octets, which the restricted ICC
--     rules read (colr.icc-*: the profile header and tag table, not the
--     tags' data); so are the reserved fields of colr boxes with other
--     METH values, and the Palette box's entries, whose length and padding
--     are cross-field rules.
--   * The contents of the XML box and of T.801's IPR box ("well-formed
--     XML", T.800 I.7.1, T.801 N.5.4) are not checked: that needs an XML
--     parser.
--   * The Reader Requirements box is modeled at layer 1 only; the server
--     ignores it, so layer 2 keeps it opaque.
--
-- Cross-field rules are at the end. The box tree rules, the JPX box rules
-- (hv_rule_child, hv_rule_url, hv_rule_flst, hv_rule_fragment_dr,
-- hv_rule_jpx, hv_rule_fragments) and the header box rules are
-- ../jpeg2000/hv_rules.c, shared by the harness (harness/crossfield_impl.h,
-- harness/crossfield.c) and the reader; the file rules (signature, ftyp,
-- one flst per ftbl, the NDR and NF counts) are implemented in both the
-- harness and ../jpeg2000/hv_reader.c (the NF count in the harness only; see
-- the end).

JP2-Boxes DEFINITIONS AUTOMATIC TAGS ::= BEGIN

EXPORTS ALL;

IMPORTS Codestream, Codestream-Profile FROM J2K-Codestream;

-- ===========================================================================
-- Layer 1: T.800 Annex I / T.801 Annex M
-- ===========================================================================

-- Box types as the big-endian value of the four-character code.
-- Superboxes and interpreted boxes:
--   jpch 0x6A706368  ftbl 0x6674626C  dtbl 0x6474626C  asoc 0x61736F63
--   jp2c 0x6A703263  flst 0x666C7374  url  0x75726C20  jp2h 0x6A703268
--   jplh 0x6A706C68  ftyp 0x66747970
--   ihdr 0x69686472  bpcc 0x62706363  colr 0x636F6C72  pclr 0x70636C72
--   cmap 0x636D6170  cdef 0x63646566  res  0x72657320  resc 0x72657363
--   resd 0x72657364
-- Opaque, permitted anywhere their level allows:
--   rreq 0x72726571  jp2i 0x6A703269  creg 0x63726567
--   jP   0x6A502020  uuid 0x75756964  xml  0x786D6C20  nlst 0x6E6C7374
--   lbl  0x6C626C20  uinf 0x75696E66  free 0x66726565
-- jp2i (Intellectual Property, T.800 I.6) and creg (Codestream
-- Registration, T.801 M.11.7.7) are opaque; their presence is what the
-- header rules count (ihdr.ipr, jpch.ipr, jpx.ipr, jpx.creg).

-- T.800 I.8 and T.801 M.12 require readers to skip box types they do not
-- understand, so both layers admit every four-cc and decode unlisted types
-- through an opaque `other` alternative (the mapping functions of
-- harness/mapping.c map them to one value, 'abcd').
BoxType ::= INTEGER (0..4294967295)

-- A JP2-family file is a sequence of top-level boxes filling the file
-- (the file is the decode region).
Jp2Family ::= SEQUENCE {
    boxes       SEQUENCE (SIZE (1..32)) OF TopBox      -- corpus bound
}

TopBox ::= SEQUENCE {
    payload     TopPayload
}

TopPayload ::= CHOICE {
    jpch        OCTET STRING (CONTAINING Superbox),
    ftbl        OCTET STRING (CONTAINING Superbox),
    dtbl        OCTET STRING (CONTAINING DataReferences),
    asoc        OCTET STRING (CONTAINING Association),
    jp2c        OCTET STRING (CONTAINING Codestream),
    jP          OCTET STRING (CONTAINING OpaqueBox),
    ftyp        OCTET STRING (CONTAINING Ftyp),
    jp2h        OCTET STRING (CONTAINING Superbox),
    jplh        OCTET STRING (CONTAINING Superbox),
    rreq        OCTET STRING (CONTAINING Rreq),
    uuid        OCTET STRING (CONTAINING OpaqueBox),
    xml         OCTET STRING (CONTAINING OpaqueBox),
    uinf        OCTET STRING (CONTAINING Superbox),
    free        OCTET STRING (CONTAINING OpaqueBox),
    jp2i        OCTET STRING (CONTAINING OpaqueBox),
    creg        OCTET STRING (CONTAINING OpaqueBox),
    cgrp        OCTET STRING (CONTAINING OpaqueBox),
    ihdr        OCTET STRING (CONTAINING OpaqueBox),
    bpcc        OCTET STRING (CONTAINING OpaqueBox),
    colr        OCTET STRING (CONTAINING OpaqueBox),
    pclr        OCTET STRING (CONTAINING OpaqueBox),
    cmap        OCTET STRING (CONTAINING OpaqueBox),
    cdef        OCTET STRING (CONTAINING OpaqueBox),
    res         OCTET STRING (CONTAINING OpaqueBox),
    nlst        OCTET STRING (CONTAINING OpaqueBox),
    lbl         OCTET STRING (CONTAINING OpaqueBox),
    other       OCTET STRING (CONTAINING OpaqueBox)
}

-- T.800 I.5.2 / T.801 Annex M, File Type box: brand, minor version, then a
-- compatibility list filling the box (so the box is >= 12 bytes and a
-- multiple of 4 by construction). Which brand is required and that the
-- list contains it depend on the file extension: cross-field rules. A
-- brand is a four-character code, as a box type is: its big-endian value.
-- The reader decodes FtypHeader, then the Brands one at a time.
Brand ::= INTEGER (0..4294967295)

Ftyp ::= SEQUENCE {
    header      FtypHeader,
    compat      SEQUENCE (SIZE (1..16)) OF Brand      -- corpus bound
}

FtypHeader ::= SEQUENCE {
    brand       Brand,
    minor       INTEGER (0..4294967295)
}

Superbox ::= SEQUENCE {
    children    SEQUENCE (SIZE (0..16)) OF InnerBox    -- fill the superbox (corpus bound)
}

-- T.801 M.11.11: association requires two or more boxes; 16 is a corpus bound.
Association ::= SEQUENCE {
    children    SEQUENCE (SIZE (2..16)) OF InnerBox
}

-- T.801 Annex M, Data Reference box: NDR then NDR url boxes.
DataReferences ::= SEQUENCE {
    ndr         DataReferenceCount,
    references  SEQUENCE (SIZE (0..64)) OF InnerBox     -- fill the box; count == ndr, each url (corpus bound)
}

DataReferenceCount ::= INTEGER (0..65535)               -- NDR (Table M.16)

OpaqueBox ::= SEQUENCE {
    data        OCTET STRING (SIZE (0..4096))           -- fills the box (corpus bound)
}

InnerBox ::= SEQUENCE {
    payload     InnerPayload
}

-- The superboxes below the top level are opaque: jpch, ftbl and dtbl so
-- that a rule names their placement (box.nested-top-level), asoc because
-- T.801 M.11.11 lets associations nest (the box tree rules read it); jp2h
-- and jplh are opaque there too.
InnerPayload ::= CHOICE {
    flst        OCTET STRING (CONTAINING FragmentList),
    url         OCTET STRING (CONTAINING DataEntryUrl),
    jpch        OCTET STRING (CONTAINING OpaqueBox),
    ftbl        OCTET STRING (CONTAINING OpaqueBox),
    dtbl        OCTET STRING (CONTAINING OpaqueBox),
    asoc        OCTET STRING (CONTAINING OpaqueBox),
    jp2h        OCTET STRING (CONTAINING OpaqueBox),
    jplh        OCTET STRING (CONTAINING OpaqueBox),
    uuid        OCTET STRING (CONTAINING OpaqueBox),
    xml         OCTET STRING (CONTAINING OpaqueBox),
    nlst        OCTET STRING (CONTAINING OpaqueBox),
    lbl         OCTET STRING (CONTAINING OpaqueBox),
    ihdr        OCTET STRING (CONTAINING Ihdr),
    colr        OCTET STRING (CONTAINING Colr),
    free        OCTET STRING (CONTAINING OpaqueBox),
    bpcc        OCTET STRING (CONTAINING Bpcc),
    res         OCTET STRING (CONTAINING Res),
    cgrp        OCTET STRING (CONTAINING Cgrp),
    pclr        OCTET STRING (CONTAINING Pclr),
    cmap        OCTET STRING (CONTAINING Cmap),
    cdef        OCTET STRING (CONTAINING Cdef),
    jp2c        OCTET STRING (CONTAINING OpaqueBox),
    jp2i        OCTET STRING (CONTAINING OpaqueBox),
    creg        OCTET STRING (CONTAINING OpaqueBox),
    other       OCTET STRING (CONTAINING OpaqueBox)
}

-- ---------------------------------------------------------------------------
-- A JP2 file, T.800 Annex I: a file whose File Type box has a brand other
-- than 'jpx ' (T.801 M.11.7.2 tells the two apart by BR). T.800 defines
-- fewer boxes than T.801, and a reader skips the boxes it does not
-- understand (T.800 I.8), so the boxes only T.801 defines (asoc, rreq,
-- jpch, ftbl, dtbl, cgrp, ...) are opaque here, at every level: a JP2 file
-- holding an asoc with one child, say, is a valid JP2 file. A JPX file
-- that lists 'jp2 ' in its compatibility list is a JP2 file too (T.800
-- I.5.2: all conforming JP2 readers "shall properly interpret all files
-- with 'jp2 ' in one of the CLi fields"; T.801 M.2.1), and is also
-- decoded as one. The UUID Info and UUID boxes are checked by the box
-- tree rules (../jpeg2000/hv_rules.c, hv_rule_box_tree), whatever their level.
-- ---------------------------------------------------------------------------

Jp2File ::= SEQUENCE {
    boxes       SEQUENCE (SIZE (1..32)) OF Jp2Box     -- fills the file (corpus bound)
}

Jp2Box ::= SEQUENCE {
    payload     Jp2Payload
}

Jp2Payload ::= CHOICE {
    jP          OCTET STRING (CONTAINING OpaqueBox),
    ftyp        OCTET STRING (CONTAINING Ftyp),
    jp2h        OCTET STRING (CONTAINING Jp2Header),
    jp2c        OCTET STRING (CONTAINING Codestream),
    other       OCTET STRING (CONTAINING OpaqueBox)
}

-- The JP2 Header box, I.5.3: its header boxes, and any other box, skipped.
Jp2Header ::= SEQUENCE {
    children    SEQUENCE (SIZE (0..16)) OF Jp2HeaderBox    -- fill the box (corpus bound)
}

Jp2HeaderBox ::= SEQUENCE {
    payload     Jp2HeaderPayload
}

Jp2HeaderPayload ::= CHOICE {
    ihdr        OCTET STRING (CONTAINING Ihdr),
    bpcc        OCTET STRING (CONTAINING Bpcc),
    colr        OCTET STRING (CONTAINING Colr),
    pclr        OCTET STRING (CONTAINING Pclr),
    cmap        OCTET STRING (CONTAINING Cmap),
    cdef        OCTET STRING (CONTAINING Cdef),
    res         OCTET STRING (CONTAINING Res),
    other       OCTET STRING (CONTAINING OpaqueBox)
}

-- ---------------------------------------------------------------------------
-- Box contents the box tree rules read one element at a time
-- (../jpeg2000/hv_rules.c, hv_rule_box_tree), in boxes the whole-file model
-- keeps opaque or does not reach.
-- ---------------------------------------------------------------------------

-- UUID List box, T.800 I.7.3.1: NU, then NU IDs filling the box.
UuidCount ::= INTEGER (0..65535)                        -- NU
UuidId ::= OCTET STRING (SIZE (16))                     -- a UUID (ISO/IEC 11578)

-- Cross-Reference box, T.801 M.11.4: Rtyp, the type of the box it stands
-- for, then a Fragment List box.
CrefType ::= INTEGER (0..4294967295)                    -- Rtyp

-- ---------------------------------------------------------------------------
-- JP2 header boxes, T.800 I.5.3 (in JPX: T.801 M.11.5 to M.11.7, in jp2h,
-- jpch and jplh). Field values are T.800's. Where T.801 admits more (C,
-- METH, EnumCS), the type takes the wider range, and what a JP2 file may
-- hold is a rule (ihdr.c, colr.method, colr.enumcs, listed at the end).
-- ---------------------------------------------------------------------------

-- A CONTAINING region's decoder skips to the region's end whatever the
-- contents left unread, so a type whose layout does not end in a deduced
-- size ends in `extra`, the bytes after its fields, which a rule requires
-- to be empty (<box>.extent). The bound is a corpus bound: in the whole-file
-- model more than 64 bytes after the fields fail to decode (reason
-- `decode`). The reader decodes Ihdr and Resolution from at most their
-- largest encoding, so any number of bytes after the fields gives
-- <box>.extent there.
Extra ::= OCTET STRING (SIZE (0..64))                     -- corpus bound

-- Image Header box, I.5.3.1: 14 bytes (the box 22, ihdr.extent).
Ihdr ::= SEQUENCE {
    height      INTEGER (1..4294967295),   -- Ysiz - YOsiz
    width       INTEGER (1..4294967295),   -- Xsiz - XOsiz
    nc          INTEGER (1..16384),        -- Csiz
    bpc         INTEGER (0..37 | 128..165 | 255),   -- common Ssiz, or 255: see bpcc
    c           INTEGER (0..255),          -- 7 (JPEG 2000); others: ihdr.c
    unkc        INTEGER (0..1),
    ipr         INTEGER (0..1),
    extra       Extra
}

-- A component or palette column's bit depth, Tables I.8 and I.13: the
-- depth minus one in the low 7 bits (1 to 38 bits), the sign in the high
-- bit. Ssiz without its reserved values.
BitDepth ::= INTEGER (0..37 | 128..165)

-- Bits Per Component box, I.5.3.2: one BitDepth per component, filling
-- the box; the count is NC.
Bpcc ::= SEQUENCE {
    depths      SEQUENCE (SIZE (1..16)) OF BitDepth     -- corpus bound; the standard's is 16,384
}

-- Colour Specification box, I.5.3.3: METH, PREC, APPROX, then EnumCS when
-- METH is 1; the rest of the box is the ICC profile when METH is 2, fields
-- T.800 reserves for other values, and, when METH is 1, nothing in a JP2
-- file or the EP parameters of T.801 M.11.7.4 in a JPX file (a rule). In a
-- JP2 file PREC and APPROX "shall be set to zero; however, conforming
-- readers shall ignore" them (I.5.3.3), a rule (colr.prec-approx); in a
-- JPX file APPROX is 1 to 4 (T.801 M.11.7.2, Table M.23: 0 "is illegal"),
-- a rule (colr.approx), and PREC any value.
ColrHeader ::= SEQUENCE {
    meth        INTEGER (0..255),          -- 1 enumerated, 2 restricted ICC; others: rules
    prec        INTEGER (-128..127),
    approx      INTEGER (0..255),
    enumcs      INTEGER (0..4294967295) OPTIONAL   -- present iff meth = 1
}

Colr ::= SEQUENCE {
    header      ColrHeader,
    rest        OCTET STRING (SIZE (0..4096))    -- fills the box (corpus bound)
}

-- Palette box, I.5.3.4: NE, NPC (the count of depths), a BitDepth per
-- column, then NE x NPC entries, each padded to whole bytes (a rule). The
-- reader decodes NE and NPC as jpeg2000-io.asn1's PclrCounts, then the
-- depths one at a time.
PclrHeader ::= SEQUENCE {
    ne          INTEGER (1..1024),
    depths      SEQUENCE (SIZE (1..255)) OF BitDepth
}

Pclr ::= SEQUENCE {
    header      PclrHeader,
    entries     OCTET STRING (SIZE (0..4096))    -- fills the box (corpus bound)
}

-- Component Mapping box, I.5.3.5: one entry per channel, filling the box.
CmapEntry ::= SEQUENCE {
    cmp         INTEGER (0..16384),        -- component index
    mtyp        INTEGER (0..1),            -- 0 direct, 1 through the palette
    pcol        INTEGER (0..255)           -- palette column; 0 when mtyp = 0 (a rule)
}

Cmap ::= SEQUENCE {
    entries     SEQUENCE (SIZE (1..16)) OF CmapEntry    -- corpus bound
}

-- Channel Definition box, I.5.3.6: N (the count of entries), then N
-- descriptions.
CdefCount ::= INTEGER (1..65535)

CdefEntry ::= SEQUENCE {
    cn          INTEGER (0..65535),        -- channel index
    typ         INTEGER (0..2 | 65535),    -- colour, opacity, premultiplied opacity, unspecified;
                                           -- 3 to 65,534 are reserved (I.5.3.6) and rejected
    asoc        INTEGER (0..65535)         -- 0 whole image, colour index, 65535 none
}

Cdef ::= SEQUENCE {
    entries     SEQUENCE (SIZE (1..16)) OF CdefEntry,   -- corpus bound; the standard's is 65,535
    extra       Extra
}

-- Resolution box, I.5.3.7: a superbox holding resc, resd or both (a rule,
-- res.resc-resd). Unknown boxes are skipped (I.8).
Res ::= SEQUENCE {
    children    SEQUENCE (SIZE (1..4)) OF ResBox        -- fill the box (corpus bound)
}

ResBox ::= SEQUENCE {
    payload     ResPayload
}

ResPayload ::= CHOICE {
    resc        OCTET STRING (CONTAINING Resolution),
    resd        OCTET STRING (CONTAINING Resolution),
    other       OCTET STRING (CONTAINING OpaqueBox)
}

-- Colour Group box, T.801 M.11.7.1: a superbox holding Colour
-- Specification boxes, at least one (a rule, cgrp.empty), only in a jplh
-- (cgrp.placement). Unknown boxes are skipped (T.800 I.8).
Cgrp ::= SEQUENCE {
    children    SEQUENCE (SIZE (0..16)) OF CgrpBox      -- fill the box (corpus bound)
}

CgrpBox ::= SEQUENCE {
    payload     CgrpPayload
}

CgrpPayload ::= CHOICE {
    colr        OCTET STRING (CONTAINING Colr),
    other       OCTET STRING (CONTAINING OpaqueBox)
}

-- Capture and Default Display Resolution boxes, I.5.3.7.1 and I.5.3.7.2:
-- grid points per meter, (VN / VD) * 10^VE and (HN / HD) * 10^HE.
Resolution ::= SEQUENCE {
    vn          INTEGER (1..65535),
    vd          INTEGER (1..65535),
    hn          INTEGER (1..65535),
    hd          INTEGER (1..65535),
    ve          INTEGER (-128..127),
    he          INTEGER (-128..127),
    extra       Extra
}

-- T.801 M.11.1, Reader Requirements box: ML, the length in bytes of every
-- mask (1, 2, 4 or 8; an ACN-inserted determinant, so the masks agree by
-- construction), the Fully Understand Aspects and Display Contents masks,
-- NSF standard features and NVF vendor features, each with its mask. SF
-- values are Table M.14's and those of extensions, so any 16-bit value.
RreqMask ::= OCTET STRING (SIZE (1 | 2 | 4 | 8))

StandardFeature ::= SEQUENCE {
    sf          FeatureCode,
    sm          RreqMask
}

VendorFeature ::= SEQUENCE {
    vf          VendorId,
    vm          RreqMask
}

FeatureCode ::= INTEGER (0..65535)                       -- SF (Table M.14)
VendorId ::= OCTET STRING (SIZE (16))                    -- VF, a UUID

Rreq ::= SEQUENCE {
    fuam        RreqMask,
    dcm         RreqMask,
    standard    SEQUENCE (SIZE (0..16)) OF StandardFeature,  -- corpus bound; the standard's is 65,535
    vendor      SEQUENCE (SIZE (0..4)) OF VendorFeature,     -- corpus bound; the standard's is 65,535
    extra       Extra
}

-- T.801 M.11.3.1, Fragment List box: NF fragments of (OFF u64, LEN u32, DR
-- u16), with the ranges of Table M.17. The reader reads NF, then the
-- fragments one at a time.
FragmentList ::= SEQUENCE {
    nf          FragmentCount,
    fragments   SEQUENCE (SIZE (0..16)) OF Fragment     -- count == nf (corpus bound)
}

FragmentCount ::= INTEGER (0..65535)                     -- NF

Fragment ::= SEQUENCE {
    off         INTEGER (12..18446744073709551615),  -- offset in the referenced file, from its
                                                     -- first byte: past the 12-byte signature box
    len         INTEGER (0..4294967295),             -- length of the fragment
    dr          INTEGER (0..65535)                   -- 0: this file; else 1-based index into dtbl
}

-- T.800 I.7.3.2, Data Entry URL box (in JPX also the entries of dtbl,
-- T.801 M.11.2): UrlHeader (VERS, FLAG), LOC (NUL-terminated), and
-- nothing after it: `extra` holds any bytes between the NUL and the end of
-- the box, which a rule requires to be empty. LOC is UTF-8 (I.7.3.2). The
-- type is IA5String because asn1scc's ACN encodes a NUL-terminated string
-- only as that; the generated code copies the bytes without checking that
-- they are 7-bit, so any UTF-8 decodes.
DataEntryUrl ::= SEQUENCE {
    header      UrlHeader,
    loc         IA5String (SIZE (0..1024)),          -- URL, NUL terminated on the wire (corpus bound)
    extra       Extra
}

-- I.7.3.2: "The value of this field shall be 0", for both.
UrlHeader ::= SEQUENCE {
    vers        INTEGER (0..0),
    flag        INTEGER (0..0)
}

-- ===========================================================================
-- Layer 2: esajpip served profile (JPIP_PROFILE.md, "Supported JPEG 2000
-- sources"). Structural rules (counts, pairing) are cross-field rules.
-- Top-level metadata superboxes that the server does not interpret are opaque
-- here; their internal box framing remains part of the standard layer only.
-- ===========================================================================

-- .jp2: exactly one jp2c, carrying a profile codestream. ReadJP2 reads
-- the signature, ftyp and jp2c boxes and skips every other box by length,
-- so every other box is opaque here, superboxes included.
Jp2File-Profile ::= SEQUENCE {
    boxes       SEQUENCE (SIZE (1..32)) OF Jp2Box-Profile
}

Jp2Box-Profile ::= SEQUENCE {
    payload     Jp2Payload-Profile
}

Jp2Payload-Profile ::= CHOICE {
    jp2c        OCTET STRING (CONTAINING Codestream-Profile),
    jP          OCTET STRING (CONTAINING OpaqueBox),
    ftyp        OCTET STRING (CONTAINING Ftyp),
    other       OCTET STRING (CONTAINING OpaqueBox)
}

-- .jpx: N jpch boxes and either N jp2c boxes (embedded) or N ftbl/flst
-- boxes plus one dtbl holding the url boxes (linked), never both. Codestreams
-- are numbered by source-box order (JPIP_PROFILE.md, "Supported JPEG 2000
-- sources"). The boxes ReadJPX skips at the top level are opaque, those
-- that belong inside another box included (as in TopPayload); flst and
-- url, which it rejects there, have no alternative.
JpxFile-Profile ::= SEQUENCE {
    boxes       SEQUENCE (SIZE (1..32)) OF TopBox-Profile
}

TopBox-Profile ::= SEQUENCE {
    payload     TopPayload-Profile
}

TopPayload-Profile ::= CHOICE {
    jpch        OCTET STRING (CONTAINING Superbox-Profile),
    ftbl        OCTET STRING (CONTAINING Superbox-Profile),
    dtbl        OCTET STRING (CONTAINING DataReferences-Profile),
    asoc        OCTET STRING (CONTAINING OpaqueBox),
    jp2c        OCTET STRING (CONTAINING Codestream-Profile),
    jP          OCTET STRING (CONTAINING OpaqueBox),
    ftyp        OCTET STRING (CONTAINING Ftyp),
    jp2h        OCTET STRING (CONTAINING OpaqueBox),
    jplh        OCTET STRING (CONTAINING OpaqueBox),
    rreq        OCTET STRING (CONTAINING OpaqueBox),
    uuid        OCTET STRING (CONTAINING OpaqueBox),
    xml         OCTET STRING (CONTAINING OpaqueBox),
    uinf        OCTET STRING (CONTAINING OpaqueBox),
    free        OCTET STRING (CONTAINING OpaqueBox),
    jp2i        OCTET STRING (CONTAINING OpaqueBox),
    creg        OCTET STRING (CONTAINING OpaqueBox),
    cgrp        OCTET STRING (CONTAINING OpaqueBox),
    ihdr        OCTET STRING (CONTAINING OpaqueBox),
    bpcc        OCTET STRING (CONTAINING OpaqueBox),
    colr        OCTET STRING (CONTAINING OpaqueBox),
    pclr        OCTET STRING (CONTAINING OpaqueBox),
    cmap        OCTET STRING (CONTAINING OpaqueBox),
    cdef        OCTET STRING (CONTAINING OpaqueBox),
    res         OCTET STRING (CONTAINING OpaqueBox),
    nlst        OCTET STRING (CONTAINING OpaqueBox),
    lbl         OCTET STRING (CONTAINING OpaqueBox),
    other       OCTET STRING (CONTAINING OpaqueBox)
}

Superbox-Profile ::= SEQUENCE {
    children    SEQUENCE (SIZE (0..16)) OF InnerBox-Profile
}

DataReferences-Profile ::= SEQUENCE {
    ndr         DataReferenceCount,
    references  SEQUENCE (SIZE (0..64)) OF InnerBox-Profile
}

InnerBox-Profile ::= SEQUENCE {
    payload     InnerPayload-Profile
}

InnerPayload-Profile ::= CHOICE {
    flst        OCTET STRING (CONTAINING FragmentList-Profile),
    url         OCTET STRING (CONTAINING DataEntryUrl-Profile),
    jpch        OCTET STRING (CONTAINING OpaqueBox),
    ftbl        OCTET STRING (CONTAINING OpaqueBox),
    dtbl        OCTET STRING (CONTAINING OpaqueBox),
    asoc        OCTET STRING (CONTAINING OpaqueBox),
    jp2h        OCTET STRING (CONTAINING OpaqueBox),
    jplh        OCTET STRING (CONTAINING OpaqueBox),
    uuid        OCTET STRING (CONTAINING OpaqueBox),
    xml         OCTET STRING (CONTAINING OpaqueBox),
    nlst        OCTET STRING (CONTAINING OpaqueBox),
    lbl         OCTET STRING (CONTAINING OpaqueBox),
    ihdr        OCTET STRING (CONTAINING OpaqueBox),
    colr        OCTET STRING (CONTAINING OpaqueBox),
    free        OCTET STRING (CONTAINING OpaqueBox),
    bpcc        OCTET STRING (CONTAINING OpaqueBox),
    res         OCTET STRING (CONTAINING OpaqueBox),
    cgrp        OCTET STRING (CONTAINING OpaqueBox),
    pclr        OCTET STRING (CONTAINING OpaqueBox),
    cmap        OCTET STRING (CONTAINING OpaqueBox),
    cdef        OCTET STRING (CONTAINING OpaqueBox),
    jp2c        OCTET STRING (CONTAINING OpaqueBox),
    jp2i        OCTET STRING (CONTAINING OpaqueBox),
    creg        OCTET STRING (CONTAINING OpaqueBox),
    other       OCTET STRING (CONTAINING OpaqueBox)
}

-- One fragment describing the complete codestream in the referenced file
-- (ReadFlstBox: box length 16, NF == 1). NF is 1 here and the list is not
-- empty; the list, `size deduced` as FragmentList's, must hold NF
-- fragments (flst.nf-count), so the box holds exactly one fragment; a byte
-- after it fails to decode. (A SIZE (1..1) list would be fixed-size, and
-- asn1scc refuses `size deduced` on a fixed-size list.)
FragmentList-Profile ::= FragmentList (WITH COMPONENTS {
    ...,
    nf (1..1),
    fragments (SIZE (1..16))
})

-- file:// URLs (ReadUrlBox). The 1,024-character bound on LOC is
-- DataEntryUrl's corpus bound; the server has no such limit.
DataEntryUrl-Profile ::= DataEntryUrl (WITH COMPONENTS {
    ...,
    loc (SIZE (8..1024))                             -- "file://" plus at least one character
})

END

-- ===========================================================================
-- Cross-field constraints for the box layer (../jpeg2000/hv_rules.c and, for
-- the file rules, harness/crossfield_impl.h, harness/crossfield.c and
-- ../jpeg2000/hv_reader.c; see the top)
-- ===========================================================================
--
-- The file's kind. At layer 1 a file whose ftyp brand is 'jpx ' is a JPX
-- file (T.801 M.11.7.2: "a file with 'jpx\040' in the BR field"), any
-- other a JP2 file (Jp2File); the extension does not matter. At layer 2
-- the extension decides, as it does for the server.
--
-- Both kinds, and both layers of a .jpx (a .jp2's layer 2 has only the
-- signature and ftyp rules, as Jp2Payload-Profile keeps every other box
-- opaque):
--   T.800 I.5.1, I.5.2: the first box is jP with payload 0D0A870A, the
--   second is ftyp.
--   T.800 I.5.2 / T.801 M.8, the brand and the compatibility list: a JP2
--     file lists 'jp2 ', whatever its brand ("If the value of the Brand
--     field is not 'jp2\040', then a value of 'jp2\040' in the
--     Compatibility list indicates that a JP2 reader can interpret the
--     file"; file.ftyp-compatibility); a JPX file has the brand 'jpx ' and
--     lists 'jpx '. The profile requires the brand of the extension,
--     'jp2 ' or 'jpx ' (ReadFileType; file.ftyp-brand) and lists it. Box
--     size and alignment are the Ftyp type's job. MinV: 0 in a JP2 file
--     (T.800 I.5.2: "The value of this field shall be zero", although
--     "readers shall continue to parse and interpret this file even if the
--     value of this field is not zero"), 1 in a JPX file (T.801 M.8);
--     file.ftyp-minor, layer 1 only: esajpip ignores MinV.
--
-- JPX (T.801), both layers:
--   M.11.2: at most one dtbl box, at the top level.
--   M.11.1: exactly one rreq box, immediately after ftyp (layer 1; the
--     profile parser ignores this writer requirement). Its contents are
--     Rreq (ML the length of every mask, NSF and NVF the counts:
--     determinants, so they agree by construction), with nothing after them
--     (rreq.extent), and no standard feature Table M.14 marks deprecated
--     ("Writers shall not include these features"; rreq.deprecated-feature).
--     That the masks describe the file's features accurately is the
--     writer's to ensure (M.11.1).
--   M.11.6: if any jpch box is present, the number of codestreams (jp2c and
--     ftbl boxes) equals the number of codestream headers; each is numbered
--     by source-box order. A file with no jpch box inherits its header
--     information from jp2h and is unconstrained here. A file with a j2cx
--     or jclx box (M.11.21, M.11.23), whose codestreams and headers M.11.6
--     counts too and the model does not read, is left out (layer 1).
--   DataReferences.references has exactly ndr elements (dtbl.ndr-count)
--     and every one is url (dtbl.non-url).
--   jp2c, jpch, ftbl and dtbl only at the top level, flst only in an ftbl,
--     url only in a dtbl, in the children of jpch, ftbl and dtbl,
--     which the server walks (hv_rule_child: jpch.nested-jp2c,
--     box.nested-jp2c, box.nested-top-level, box.flst-placement,
--     box.url-placement, dtbl.non-url). Everywhere else at layer 1: the box
--     tree rules, below.
--   FragmentList.fragments has exactly nf elements (flst.nf-count in the
--     harness and standard reader). At the profile layer,
--     FragmentList-Profile rejects any NF but 1 first (flst.one-fragment).
--   UrlHeader's VERS and FLAG are 0 (I.7.3.2): a type constraint, reason
--     `decode`; the reader names it url.version-flags (hv_rules.c).
--   DataEntryUrl.loc contains no NUL (the wire terminator is not part of
--     loc) and may be empty, and the box ends right after the terminator:
--     `extra` is empty (box.extent at layer 1; at layer 2 hv_rule_url sees
--     the bytes after the NUL and names it url.terminator, as the reader
--     does).
--   Every Fragment.dr is 0 or <= the file's ndr (flst.dr-range). Checked
--     after the count rules (hv_rule_jpx), in the reader's order.
--   T.801 M.11.3, Fragment Table box: it contains exactly one flst box
--     (ftbl.one-flst).
--   Every CONTAINING region is exactly filled. Where the type ends in a
--     deduced size this is automatic; Ihdr, Cdef, Resolution, Rreq and
--     DataEntryUrl end in `extra`, which must be empty (<box>.extent: the
--     decoder skips to the end of a region whatever its contents left
--     unread).
--
-- The box tree, layer 1 only (hv_rule_box_tree, on the file's bytes; its
-- header gives each rule and clause): every box of every superbox the
-- file's kind defines, to HV_BOX_DEPTH_MAX levels.
--   Both kinds: jP and ftyp once (file.one-signature, file.one-ftyp); jp2h
--     and uinf only at the top level (box.nested-top-level); bpcc, pclr,
--     cmap, cdef and res not at the top level, nor colr in a JP2 file
--     (box.top-level; T.800 I.2.2, Figure I.1, which "specifies ... the
--     containment relationship between the boxes"; an ihdr elsewhere
--     "shall be ignored", I.5.3.1, and T.801 states no such rule for the
--     boxes it adds); a uinf holds a ulst, then a url (uinf.contents), a
--     ulst NU UUIDs (ulst.nu-count), a uuid box a 16-byte UUID (uuid.id),
--     and a url in a uinf (or a JPX file's dtbl) VERS and FLAG 0 and LOC
--     NUL-terminated at its end (url.version-flags, url.terminator,
--     box.extent).
--   JP2 (T.800): jp2c only at the top level (box.nested-jp2c), url only in
--     a uinf (box.url-placement), and bpcc, colr, pclr, cmap, cdef and res
--     only in jp2h, resc and resd only in res, ulst only in uinf
--     (box.containment; Figure I.1); every box T.801 adds is one a reader
--     skips (I.8), its contents unread.
--   JPX (T.801): dtbl, rreq, comp and jclx only at the top level, jpch and
--     jplh there or in a jclx, ftbl and j2cx there or in a j2cx, jp2c there
--     or in a j2cx (box.nested-top-level, box.nested-jp2c,
--     jpch.nested-jp2c), the top-level jp2c and ftbl before any j2cx
--     (j2cx.order, M.11.23), the top-level jpch and jplh, and comp,
--     before any jclx, and with a jclx at least one of each (jclx.order,
--     jclx.headers; M.11.6, M.11.7, M.11.21); in a j2cx a j2ci first, of
--     8 bytes, and nowhere else (j2ci.placement, j2ci.length), then its
--     codestreams, then mdat and free boxes (j2cx.contents), Ncs its
--     codestreams (j2ci.ncs), the sub-boxes as Ltbl describes them
--     (j2ci.ltbl), and with a j2cx a top-level codestream, one for each
--     top-level jplh without creg (j2cx.top-codestreams; M.11.23,
--     M.11.24); in a jclx a jlxi first, of 20 bytes or 24 with T, and
--     nowhere else (jlxi.placement, jlxi.length), then its jpch, then its
--     compositing groups of jplh then inst boxes, only the last without
--     inst, then other boxes (jclx.contents), C, L and T its jpch, jplh
--     and groups with inst (jlxi.counts), M 0 only with C and in the last
--     jclx (jlxi.repetition), F 0 with T only in the last (jlxi.frames;
--     M.11.21, M.11.22); a grp not the first box of an asoc
--     (grp.placement, M.11.25); flst only in an ftbl, url only in a dtbl
--     or a uinf, only url in a dtbl (box.flst-placement, box.url-placement,
--     dtbl.non-url); cgrp only in a jplh (cgrp.placement), colr only in
--     jp2h or a cgrp (colr.placement), opct and creg only in a jplh, at
--     most one each there, and no cdef with an opct (opct.placement,
--     opct.once, opct.cdef, creg.placement, creg.once), at most one pxfm
--     in each jp2h or jplh (pxfm.once), cref only in a jpch, jplh or asoc
--     (cref.placement), at most one comp, copt its first box and nowhere
--     else (comp.once, comp.copt-first, copt.placement), inst only in comp
--     or jclx (inst.placement, M.11.10.2), at most one drep,
--     gtso only in it and once (drep.once, gtso.placement, gtso.once), two
--     or more boxes in an asoc (asoc.children), a lbl of UTF-8 without the
--     characters M.11.13 excludes (lbl.characters), one flst in an ftbl
--     (ftbl.one-flst), and a colr in jp2h or a cgrp (jpx.colr).
--   A box inside a superbox framed as hv_boxes_next does not accept:
--     box.framing.
-- The fragments in the file, JPX, layer 1 (hv_rule_fragments): each flst,
--   including those inside j2cx, has exactly NF complete tuples
--   (flst.nf-count), valid Fragment fields (decode), and DR <= NDR
--   (flst.dr-range). Each fragment with DR 0 of each ftbl's flst (at the
--   top level or in a j2cx) is within the payload of one mdat box (T.801 M.4; flst.mdat), the first at
--   its codestream's SOC (M.11.3.1; flst.codestream-start).
--
-- Header boxes, standard layer only (hv_rules.c; the reader's
-- hv_check_jp2h and hv_check_jpx_headers). The server reads none of them:
-- Jp2Payload-Profile and TopPayload-Profile keep jp2h and jplh opaque, and
-- jpch's children are InnerBox-Profile, whose header boxes are opaque.
--   JP2 file (T.800 I.2, I.5.3, I.5.4): one or more top-level jp2c
--     (jp2.one-codestream, the profile's name for its stricter "exactly
--     one"); exactly one jp2h (jp2.one-jp2h; I.5.3: "one and only one"),
--     before the first jp2c (jp2h.position).
--   JPX file (T.801 M.11.5): jp2h optional, anywhere at the top level
--     ("the JPX file format allows the JP2 Header box to be located
--     anywhere at the top-level of the file"), at most one (jpx.one-jp2h:
--     M.11.5 lets a JPX file omit the JP2 Header box of T.800 I.5.3, "one
--     and only one"); in a baseline file, with 'jpxb' in the list, before
--     the first jp2c, ftbl, mdat, jpch and jplh (jp2h.position; M.9.2.7).
--   jp2h starts with ihdr (jp2h.ihdr-first) and holds its colr boxes
--     contiguously (jp2h.colr-contiguous). A header box holds at most one
--     bpcc, pclr, cmap, cdef and res (header.one-<box>); a jpch at most one
--     ihdr (header.one-ihdr; elsewhere a second ihdr is ignored, I.5.3.1).
--   ihdr: C 7 in a JP2 file (I.5.3.1), 0 to 12 in a JPX file (Table M.19),
--     and 7 for a JPEG 2000 codestream at hand (ihdr.c).
--   colr: when METH is 1, nothing after EnumCS, except in a JPX file the EP
--     parameters (T.801 M.11.7.4): 28 bytes for EnumCS 14 (CIELab), 24 for
--     EnumCS 19 (CIEJab), or none (colr.enumcs-length). When METH is 2, a
--     restricted ICC profile (T.800 Table I.9): its header's size the
--     PROFILE's and the signature 'acsp' (colr.icc-header), the input
--     class 'scnr' with the colourspace 'GRAY' or 'RGB ' (colr.icc-class),
--     the PCS 'XYZ ' (colr.icc-pcs), and the tags ICC.1:1998-09 requires of
--     the Monochrome Input or Three-Component Matrix-Based Input class in
--     its tag table, each within the profile (colr.icc-tags). JP2: PREC and
--     APPROX 0 in every colr (colr.prec-approx, I.5.3.3). JP2, and the
--     jp2h of a JPX file that lists 'jp2 ' (T.801 M.3.6): the first colr of
--     jp2h METH 1 or 2 (colr.method) and, if 1, EnumCS 16, 17 or 18
--     (colr.enumcs); a reader ignores a colr of another METH (I.5.3.3).
--     JPX: APPROX 1 to 4 in every colr of METH 1 to 5 (colr.approx,
--     M.11.7.2), and no two enumerated and no two restricted ICC colr in
--     jp2h or in a cgrp
--     (colr.one-method, M.11.7.1).
--   cgrp (T.801 M.11.7.1), JPX only: at least one colr (cgrp.empty), each
--     checked as a colr in jp2h (colr.*). In a JP2 file, where T.800 does
--     not define it, a cgrp is a box a reader skips.
--   IPR (T.800 I.5.3.1, T.801 M.11.5.1, M.11.6): in a JP2 file, the ihdr's
--     IPR is 1 exactly when the file holds an IPR box, anywhere the box
--     tree reads (I.6: "IPR boxes may be found at other locations";
--     ihdr.ipr); in a JPX file, a jpch holds no jp2i when the codestream's
--     ihdr (its own, or jp2h's) has IPR 0 (jpch.ipr), and a codestream
--     whose ihdr has IPR 1 has an IPR box, or a cref for one, in the file
--     (jpx.ipr).
--   creg (T.801 M.11.7.7): if any jplh holds a creg, every jplh does
--     (jpx.creg).
--   pclr: NE x NPC entries, each of its column's depth padded with zero
--     bits to whole bytes (pclr.entries-length, pclr.padding; I.5.3.4).
--   cmap: PCOL 0 when MTYP is 0 (cmap.pcol-zero).
--   cdef (I.5.3.6): no two channels with the same Typ and Asoc, except
--     where either is 65535 (cdef.pairs; a box "may specify multiple
--     descriptions for a single channel"); at most one opacity or
--     premultiplied opacity channel for each colour, an opacity channel of
--     the whole image (Asoc 0) standing for every colour (cdef.opacity).
--     These two restrictions apply only to headers used by a JP2 reader:
--     jp2h in JP2 or JP2-compatible JPX. T.801 M.11.7.5 relaxes both for
--     JPX-only headers, including jpch and jplh of JP2-compatible JPX.
--   res: resc, resd or both (res.resc-resd).
--   The header of each codestream: in a JP2 file jp2h; in a JPX file
--     codestream k's jpch over jp2h's defaults (M.11.6), or jp2h alone when
--     there is no jpch.
--     JP2: at least one colr (jp2h.colr); bpcc exactly when BPC is 255
--       (ihdr.bpcc); pclr exactly with cmap (header.pclr-cmap).
--     JPX: an ihdr in jpch or jp2h (jpch.ihdr); bpcc in the ihdr's own box
--       when BPC is 255 (ihdr.bpcc; M.11.5.1); pclr needs cmap and an MTYP
--       1 entry needs pclr (header.pclr-cmap).
--     Both: bpcc has NC entries (bpcc.count); cmap components below NC
--       (cmap.component) and palette columns below NPC
--       (cmap.palette-column).
--     JP2, the channels: cdef channels below the channel count, cmap's or
--       NC (cdef.channel); every channel and every colour is defined
--       when cdef is present (cdef.complete; I.5.3.6); opacity from unsigned components or palette
--       columns (cdef.opacity-signed; Table I.16); Asoc a colour of the
--       first colr's colourspace, where it gives one (cdef.asoc; Table
--       I.18); with the codestream's multiple component transform, an RGB
--       colourspace and R, G and B as channels 0, 1 and 2
--       (jp2.mct-colourspace).
--     Against the codestream's SIZ (T.800 I.5.3.1, I.5.3.2), where the
--       codestream is in the file: a T.800 codestream in a JP2 file
--       (jp2.rsiz); HEIGHT = Ysiz - YOsiz (ihdr.height), WIDTH = Xsiz -
--       XOsiz (ihdr.width), NC = Csiz (ihdr.nc), BPC the components' common
--       Ssiz or 255 when they differ (ihdr.bpc), each bpcc entry the
--       component's Ssiz (bpcc.depth); in a JPX file not the last two where
--       the codestream signals the Part 2 multiple component or non-linear
--       point transformation (T.801 Table A.2, M.11.5.1 NOTE).
--   A JPX file that lists 'jp2 ' (T.800 I.5.2: "all conforming readers
--     shall properly interpret all files with 'jp2\040' in one of the CLi
--     fields"): also the JP2 file's rules on jp2h's place and on its header
--     against the first codestream, but for IPR, whose semantics T.801
--     M.11.5.1 redefines for a JPX file.
--   A baseline JPX file, with 'jpxb' (T.801 M.9.2): besides jp2h.position,
--     the first compositing layer's colour specifications (the first
--     jplh's cgrp, else jp2h's) include one of a method M.9.2.4 lists and
--     one with APPROX 3 or less (jpxb.colour); the first jpch and the first
--     jplh hold no header box of a type jp2h holds (jpxb.header-override;
--     M.9.2.7); the first codestream's fragments are in the file, in order
--     (jpxb.fragments; M.9.2.5).
--   Not checked: that cdef is absent when the channels are the colours in
--     order (I.5.3.6); opct against
--     cdef; the header of a linked codestream against the linked file's
--     SIZ; the boxes a cref stands for; the baseline rules on compositing
--     layers, codestreams and cross-references (M.9.2.2, M.9.2.3, M.9.2.6),
--     which need the creg and cref contents and T.801's marker segments;
--     J2P0 and J2P1 in a JP2 file's list (I.5.2), which restrict the first
--     codestream to a profile; the contents of the XML and IPR boxes.
--
-- Profile only (ReadJP2 / ReadJPX):
--   Jp2File-Profile: exactly one jp2c among the top-level boxes
--     (jp2.one-codestream).
--   JpxFile-Profile: at least one jpch box (jpx.no-jpch), where the
--     standard lets a JPX file fall back on jp2h. jp2c boxes and ftbl boxes
--     do not both occur (jpx.mixed-sources); the standard allows a file to
--     hold some codestreams inline and others by reference. Linked: exactly
--     one top-level dtbl (jpx.linked-shape) and every flst's dr in 1..ndr
--     (flst.dr-external, and flst.dr-range above). A linked file without a
--     dtbl breaks one of the dr rules too, so jpx.linked-shape comes first
--     only because the count rules are checked before the dr rules, as in
--     the reader; its vector holds its codestreams in mdat boxes (DR 0),
--     standard-valid.
--     (ReadJPX; the order of jp2c relative to jpch is not constrained.)
--   These JPX rules apply to .jpx files only; ReadJP2 looks at nothing but
--     jp2c boxes.
--   Every url loc begins with "file://" and ends with ".jp2" (ReadJPX: links
--     resolve to .jp2 files only, never to another JPX): url.file-scheme,
--     url.jp2-target; the harness resolves it against the corpus companion
--     files (url.missing-companion, harness/label.c).
--   Types, not rules, in the harness: DataEntryUrl-Profile (LOC of 8 or
--     more characters) and FragmentList-Profile (one fragment) reject
--     first, with reason `decode`; the reader names these url.length and
--     flst.one-fragment (hv_rules.c), and the harness checks that the rules
--     and the types agree (check_profile_rule_parity), as it does for
--     url.version-flags at layer 1.
--   Fragment (off, len) equal to the referenced file's codestream extent is
--     checked by the server against the linked file, and by the harness
--     against the companion's measured extent (flst.source-extent,
--     harness/label.c).
--   The whole file is <= INT_MAX bytes (file.size-limit, reader only: the
--     corpus has no such file).
