-- j2k-codestream.asn1
--
-- Framing of a JPEG 2000 Part 1 codestream (ITU-T T.800 Annex A): SOC, the
-- main header, tile-parts, EOC. Marker segment bodies come from
-- j2k-headers.asn1. This module is what makes a generated vector a complete
-- codestream rather than a loose marker body.
--
-- Design rules (encodings in j2k-codestream.acn):
--   * No length is an ASN.1 field. Every Lxxx and Psot is an ACN-inserted
--     determinant of an OCTET STRING (CONTAINING ...) with a mapping
--     function for the standard's offset (Lxxx counts itself: +2; Psot
--     counts from the SOT marker code: +12). On encode the value is
--     computed by deferred patching; on decode it bounds the region.
--     Invalid-length vectors are produced by byte mutation.
--   * Each segment kind is its own SEQUENCE wrapper so that its inserted
--     length has a home. A segment list element is a SEQUENCE of the
--     marker `code` and one OPTIONAL wrapper per kind, and ACN present-when
--     on `code` makes the matching wrapper present.
--   * Lists terminated by a marker rather than counted use ACN
--     `size null-terminated` with the marker as termination pattern. The
--     pattern is inspected only at element boundaries, where the next bytes
--     are always a marker code, so this is sound.
--   * The type graph is not recursive (asn1scc requirement): main-header
--     segments and tile-part-header segments are different SEQUENCEs, which
--     also encodes T.800 Table A.2's placement rules.
--   * The profile layer repeats the framing where a body narrows (SIZ,
--     COD: *-Profile segments), because a WITH COMPONENTS subtype cannot
--     swap the type inside a CONTAINING; PLT segments are layer 1's.
--     QCD and COM bodies stay opaque in the served profile.
--
-- Not modeled: Psot = 0 ("tile-part extends to EOC", A.4.2), because a
-- region cannot be both determinant-sized and deduced; the server accepts
-- it (README.md, "Gaps"). Bounds marked "corpus bound" are smaller than
-- the standard's because asn1scc allocates every maximum inline; see the
-- note in j2k-headers.asn1.

J2K-Codestream DEFINITIONS AUTOMATIC TAGS ::= BEGIN

EXPORTS ALL;

IMPORTS
    Siz, Cod, Qcd, Plt, Com, Siz-Profile, Cod-Profile
        FROM J2K-Headers;

-- ===========================================================================
-- Layer 1: ITU-T T.800 Annex A
-- ===========================================================================

-- Marker codes, Table A.2. Delimiting: SOC FF4F, SOT FF90, SOD FF93,
-- EOC FFD9. Fixed information: SIZ FF51. Functional: COD FF52, COC FF53,
-- QCD FF5C, QCC FF5D, RGN FF5E, POC FF5F. Pointer: TLM FF55, PLM FF57,
-- PLT FF58, PPM FF60, PPT FF61. Informational: CRG FF63, COM FF64.
--
-- Both layers skip a marker segment T.800 does not specify by its length in
-- the main header, and layer 1 in a tile-part header too, through an
-- `other` alternative selected by a negated present-when (ACN
-- 4.9 boolean expressions): "When a marker segment that is not specified
-- in the Recommendation | International Standard appears in a codestream,
-- the decoder shall use the length parameter to discard the marker
-- segment" (A.1). Layer 1 also takes the markers 0xFF30 to 0xFF3F, which
-- have no segment and "shall be skipped by the decoder" (A.1.3), as
-- `noSegment`; it leaves out only the codes Table A.2 places elsewhere, and
-- 0xFF00 and 0xFFFF, which are not markers (A.1). The profile (layer 2)
-- leaves out COC, POC, PPM and 0xFF30 to 0xFF3F too
-- (MainMarkerCode-Profile). Each value set is the codes whose field ACN
-- makes present: spec/check-model.sh checks that every code of it selects
-- exactly one field. The four types have their own ACN encoding (16 bits,
-- big-endian), so their generated decoders, which the reader could call,
-- read a marker code.

-- Every marker but SOC FF4F, SIZ FF51, PLT FF58, PPT FF61, SOP FF91, EPH
-- FF92, SOD FF93 and EOC FFD9, which ends the list.
MainMarkerCode ::= INTEGER (65281..65358 | 65360 | 65362..65367 | 65369..65376 |
                            65378..65424 | 65428..65496 | 65498..65534)

-- Every marker but SOC, SIZ, TLM FF55, PLM FF57, PPM FF60, CRG FF63, SOT
-- FF90, SOP, EPH, SOD, which ends the list, and EOC.
TileMarkerCode ::= INTEGER (65281..65358 | 65360 | 65362..65364 | 65366 |
                            65368..65375 | 65377..65378 | 65380..65423 |
                            65428..65496 | 65498..65534)

-- T.800 A.4.4 / I.5.4: EOC ends the jp2c payload. CONTAINING bounds
-- decoding but skips unread bytes, so extra captures the tail for the
-- codestream.extent rule in both layers. Its 64-byte bound is a corpus
-- bound; larger tails fail to decode. Valid codestreams encode no extra bytes.
Codestream ::= SEQUENCE {
    soc         INTEGER (65359..65359),       -- FF4F
    sizCode     INTEGER (65361..65361),       -- FF51: SIZ is always first (A.3)
    siz         SizSegment,
    segments    SEQUENCE (SIZE (1..80)) OF MainSegment,    -- terminated by EOC (corpus bound)
    extra       OCTET STRING (SIZE (0..64))               -- after EOC; must be empty
}

-- One wrapper per segment kind: the ACN-inserted Lxxx lives in the wrapper.
-- The reader/writer decodes and encodes COD and QCD whole with these
-- CodSegment and QcdSegment (see jpeg2000-io.asn1).
SizSegment ::= SEQUENCE { body OCTET STRING (CONTAINING Siz) }
CodSegment ::= SEQUENCE { body OCTET STRING (CONTAINING Cod) }
QcdSegment ::= SEQUENCE { body OCTET STRING (CONTAINING Qcd) }
PltSegment ::= SEQUENCE { body OCTET STRING (CONTAINING Plt) }
ComSegment ::= SEQUENCE { body OCTET STRING (CONTAINING Com) }
OpaqueSegment ::= SEQUENCE { body OCTET STRING (CONTAINING Opaque) }

-- Everything the server skips by length. Bounded for the corpus.
Opaque ::= SEQUENCE {
    data        OCTET STRING (SIZE (0..4096))            -- corpus bound
}

MainSegment ::= SEQUENCE {
    code        MainMarkerCode,
    cod         CodSegment OPTIONAL,
    coc         OpaqueSegment OPTIONAL,
    qcd         QcdSegment OPTIONAL,
    qcc         OpaqueSegment OPTIONAL,
    rgn         OpaqueSegment OPTIONAL,
    poc         OpaqueSegment OPTIONAL,
    tlm         OpaqueSegment OPTIONAL,
    plm         OpaqueSegment OPTIONAL,
    ppm         OpaqueSegment OPTIONAL,
    crg         OpaqueSegment OPTIONAL,
    com         ComSegment OPTIONAL,
    tilePart    TilePart OPTIONAL,
    noSegment   NULL OPTIONAL,                -- 0xFF30 to 0xFF3F
    other       OpaqueSegment OPTIONAL        -- any other code: skipped by length
}

-- SOT marker segment (A.4.2) with the tile-part header and data that
-- Psot covers. Psot is ACN-inserted between isot and tpsot.
TilePart ::= SEQUENCE {
    lsot        INTEGER (10..10),
    isot        INTEGER (0..65534),           -- tile index
    tpsot       INTEGER (0..254),             -- tile-part index (255 reserved)
    tnsot       INTEGER (0..255),             -- number of tile-parts; 0 = not specified
    rest        OCTET STRING (CONTAINING TilePartRest)   -- sized by Psot - 12
}

TilePartRest ::= SEQUENCE {
    headers     SEQUENCE (SIZE (0..8)) OF TileSegment,    -- terminated by SOD (corpus bound)
    data        OCTET STRING (SIZE (0..4096))             -- to the end of the tile-part (corpus bound)
}

TileSegment ::= SEQUENCE {
    code        TileMarkerCode,
    cod         CodSegment OPTIONAL,
    coc         OpaqueSegment OPTIONAL,
    qcd         QcdSegment OPTIONAL,
    qcc         OpaqueSegment OPTIONAL,
    rgn         OpaqueSegment OPTIONAL,
    poc         OpaqueSegment OPTIONAL,
    plt         PltSegment OPTIONAL,
    ppt         OpaqueSegment OPTIONAL,
    com         ComSegment OPTIONAL,
    noSegment   NULL OPTIONAL,                -- 0xFF30 to 0xFF3F
    other       OpaqueSegment OPTIONAL        -- any other code: skipped by length
}

-- ===========================================================================
-- Layer 2: esajpip served profile (same framing, profile SIZ and COD)
-- ===========================================================================

-- Any marker code the server tolerates in that position; the listed
-- alternatives are interpreted, everything else is `other` (skipped by
-- length). Outside the value set:
--   COC (FF53) and POC (FF5F): the server rejects them because packet
--     indexing is derived from the main COD alone.
--   PPM (FF60): it moves the packet headers into the main header, so the
--     precinct data-bins, built from the tile-part data, would hold packet
--     bodies without their headers.
--   SOC, SIZ, PLT, PPT, SOP, EPH, SOD and EOC: T.800 defines them for
--     other positions (Table A.2).
--   FF30 to FF3F: markers without a segment (A.1.3), so they cannot be
--     skipped by length, and T.800 leaves open whether skipping them is
--     harmless; the profile rejects them.
MainMarkerCode-Profile ::= INTEGER (65281..65327 | 65344..65358 | 65360 | 65362 |
                                    65364..65367 | 65369..65374 | 65378..65424 |
                                    65428..65496 | 65498..65534)
-- PLT is the only tile-header segment the server accepts (the served
-- tile-header data-bin is empty, so nothing else could reach the client).
TileMarkerCode-Profile ::= INTEGER (65368..65368)

Codestream-Profile ::= SEQUENCE {
    soc         INTEGER (65359..65359),
    sizCode     INTEGER (65361..65361),
    siz         SizSegment-Profile,
    segments    SEQUENCE (SIZE (3..80)) OF MainSegment-Profile,    -- >= COD, QCD, one tile-part (corpus bound)
    extra       OCTET STRING (SIZE (0..64))                      -- after EOC; must be empty
}

SizSegment-Profile ::= SEQUENCE { body OCTET STRING (CONTAINING Siz-Profile) }
CodSegment-Profile ::= SEQUENCE { body OCTET STRING (CONTAINING Cod-Profile) }

MainSegment-Profile ::= SEQUENCE {
    code        MainMarkerCode-Profile,
    cod         CodSegment-Profile OPTIONAL,
    qcd         OpaqueSegment OPTIONAL,
    qcc         OpaqueSegment OPTIONAL,
    rgn         OpaqueSegment OPTIONAL,
    tlm         OpaqueSegment OPTIONAL,
    plm         OpaqueSegment OPTIONAL,
    crg         OpaqueSegment OPTIONAL,
    com         OpaqueSegment OPTIONAL,
    tilePart    TilePart-Profile OPTIONAL,
    other       OpaqueSegment OPTIONAL        -- any other code: skipped by length
}

TilePart-Profile ::= SEQUENCE {
    lsot        INTEGER (10..10),
    isot        INTEGER (0..0),               -- single tile
    tpsot       INTEGER (0..63),              -- at most 64 tile-parts (PacketIndex::MAX_SEGMENTS)
    tnsot       INTEGER (0..64),
    rest        OCTET STRING (CONTAINING TilePartRest-Profile)
}

TilePartRest-Profile ::= SEQUENCE {
    headers     SEQUENCE (SIZE (0..8)) OF TileSegment-Profile,     -- corpus bound
    data        OCTET STRING (SIZE (0..4096))                      -- corpus bound
}

TileSegment-Profile ::= SEQUENCE {
    code        TileMarkerCode-Profile,
    plt         PltSegment OPTIONAL           -- the only code TileMarkerCode-Profile admits
}

END

-- ===========================================================================
-- Cross-field constraints for the framing (the tile-part rules sot.*, the
-- tile-part limit and the packet count are ../jpeg2000/hv_rules.c, shared by
-- the harness and the reader; the placement and count of segments are
-- implemented in both, harness/crossfield_impl.h and ../jpeg2000/hv_reader.c)
-- ===========================================================================
--
-- Standard (both layers), T.800 A.3 and Table A.2:
--   Codestream.segments holds exactly one COD and exactly one QCD before the
--     first tilePart (COC/QCC may repeat), and at least one tilePart.
--   After the first tilePart, every element of Codestream.segments is a
--     tilePart (A.3: only SOT and EOC follow tile-part data). The main list
--     admits other kinds structurally; the rule rejects them.
--   isot is a tile of the grid SIZ describes (A.4.2: tiles in raster order
--     from 0).
--   For each tile: tile-part indices tpsot are 0, 1, 2, ... in stream order;
--     every non-zero tnsot of that tile is the same value, tpsot < tnsot for
--     every tile-part of that tile, and the tile's tile-part count == tnsot.
--   COD and QCD appear in a tile-part header at most once each, and only in
--     the first tile-part of the tile (A.6.1, A.6.4).
--   The OPTIONAL that is present is the one `code` selects (automatic:
--     present-when). A code with no field of its own would decode with
--     none present, but no such code is in the MainMarkerCode or
--     TileMarkerCode value set (spec/check-model.sh), so the decoder's
--     constraint check rejects it: reason `decode`, where the reader says
--     main.marker-code. The harness has no C rule for it.
--   Lengths and region fills: automatic (CONTAINING + size deduced).
--   The bodies the framing keeps opaque (COC, QCC, RGN, POC, TLM, PLM, PPM,
--     PPT, CRG), and what the segments and the tile-part data come to
--     across headers: standard layer only, listed at the end of
--     j2k-headers.asn1 (hv_segments in ../jpeg2000/hv_rules.c).
--   Where a single unsubsampled tile with zero image and tile origins uses
--     COD without packet-layout overrides and every tile-part has PLT, the
--     nonzero Iplt count matches the packet count.
--
-- Profile only:
--   (Types, not rules: MainMarkerCode-Profile excludes COC, POC, PPM, the
--     codes T.800 defines for other positions and FF30 to FF3F, and
--     TileMarkerCode-Profile / TileSegment-Profile admit only PLT, so a tile
--     header carrying COD, QCD, COM or anything else fails to decode at
--     layer 2; Siz-Profile and Cod-Profile narrow SIZ and COD,
--     j2k-headers.asn1.)
--   1..64 tile-parts in total (single tile, so per tile == total). In the
--     harness TilePart-Profile's TPsot (0..63) and TNsot (0..64) reject a
--     65th tile-part first (reason `decode`); the reader names it
--     codestream.tile-part-limit (HV_PROFILE_TILE_PARTS, which
--     spec/check-model.sh compares with TilePart-Profile).
--   Every tile-part header holds at least one PLT segment (ReadSODMarker).
--   Each COD-derived packet has a nonzero Iplt; only zero entries after the
--     final packet are accepted as deployed-file padding.
--   Whole codestream <= INT_MAX bytes.
