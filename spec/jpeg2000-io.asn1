-- jpeg2000-io.asn1
--
-- Header types for the JPEG 2000 reader/writer in ../jpeg2000 (hv_reader,
-- hv_writer), which hv_walk, hv_transcode and hv_merge use.
-- Unlike the whole-file model (j2k-codestream.asn1, jp2-boxes.asn1), these
-- types are decoded and encoded one at a time by a hand-written walker that
-- steps from header to header. A payload (box contents, tile-part data) is
-- never an ASN.1 value: asn1scc gives every OCTET STRING an inline array of
-- its maximum size, clears it on initialization and copies into it on
-- decode. The walker records where a payload starts and how long it is.
--
-- The lengths that decide how far a payload runs (LBox, XLBox, Psot) are
-- ASN.1 fields here, not ACN determinants. That is what lets this module
-- state the forms the whole-file model cannot: LBox = 0 and Psot = 0 ("to
-- the end"), and LBox = 1 with XLBox. (ACN selects a CHOICE alternative
-- only by `field == value`, so there is no "otherwise" alternative, and
-- `size deduced` cannot sit inside a CHOICE alternative.) The generated
-- code checks the values; the walker turns them into extents.
--
-- One element at a time. Every type here is small: a fixed part or one
-- element of a list. A list is never a value of this module: the walker
-- decodes its elements one at a time, up to the end the segment or box
-- length gives, and the writer encodes them one at a time and measures the
-- length it wrote. So no C struct is sized by the standard's bound on a
-- list (16,384 components, 65,532 packet lengths, 65,535 features), no
-- encoder needs more room than one element, and no length in C depends on
-- how the model states a count.
--
-- Shared, not copied. The fixed parts and elements are the whole-file
-- model's own types (SizFixed, Component, Zplt, Iplt, Rcom, FtypHeader,
-- Brand, DataReferenceCount, UrlHeader, FragmentCount, Fragment, BitDepth
-- and the header box entries), and COD and QCD, at most 45 and 197 bytes,
-- are decoded whole as j2k-codestream.asn1's CodSegment and QcdSegment,
-- Lxxx included. This module defines only what the whole-file model cannot
-- lend: the forms of a length it cannot state (BoxHeader, SotSegment), a
-- marker code and Lxxx on their own, and copies where the whole-file model
-- passes an ACN parameter the element cannot take on its own (the Reader
-- Requirements masks, sized by ML) or holds a count only as an ACN
-- determinant (the palette's NPC), and a Number List entry, which the
-- whole-file model keeps opaque. spec/check-model.sh compares each copy
-- with its original, SotSegment with TilePart included.
--
-- Struct sizes (asn1scc 4.9.3.0, C, 64-bit): see ../jpeg2000/README.md, "Struct
-- sizes".

JPEG2000-IO DEFINITIONS AUTOMATIC TAGS ::= BEGIN

EXPORTS ALL;

IMPORTS
    RreqMask, FeatureCode, VendorId
        FROM JP2-Boxes;

-- ---------------------------------------------------------------------------
-- Box header, T.800 I.4: LBox, TBox, and XLBox when LBox = 1
-- ---------------------------------------------------------------------------

BoxHeader ::= SEQUENCE {
    lbox        INTEGER (0..1 | 8..4294967295),   -- 0: the box runs to the end of the file
                                                  -- 1: the length is in xlbox
                                                  -- otherwise: box length, header included
    tbox        INTEGER (0..4294967295),          -- box type, four bytes big-endian
    xlbox       INTEGER (16..18446744073709551615) OPTIONAL   -- present iff lbox = 1
}

-- ---------------------------------------------------------------------------
-- Codestream markers, T.800 A.1.1
-- ---------------------------------------------------------------------------

-- 0xFF followed by 0x01..0xFE (the range the profile layer also uses).
MarkerCode ::= INTEGER (65281..65534)

-- Lxxx of any marker segment. It counts its own two bytes.
SegmentLength ::= INTEGER (2..65535)

-- COD and QCD are decoded whole with j2k-codestream.asn1's CodSegment and
-- QcdSegment (Lxxx, then the body it sizes). SIZ, PLT and COM are read
-- after SegmentLength, one element at a time (j2k-headers.asn1): SIZ as
-- SizFixed, then Csiz Components (checked in the profile as
-- SizFixed-Profile and Component-Profile, the two parts of Siz-Profile);
-- PLT as Zplt, then Iplts to the end of the segment; COM as Rcom, then the
-- text, which stays in place.

-- ---------------------------------------------------------------------------
-- JPX boxes, T.801 Annex M, read one box at a time
-- ---------------------------------------------------------------------------

-- The Data Reference box (M.11.2), the Data Entry URL box and the Fragment
-- List box (M.11.3.1) are read with jp2-boxes.asn1's types: NDR
-- (DataReferenceCount), then the url boxes; UrlHeader (VERS, FLAG), then
-- LOC, a NUL-terminated string filling the rest of the box, which the
-- walker checks (hv_rule_url); NF (FragmentCount), then the Fragments.

-- Reader Requirements box (M.11.1), one part at a time: RreqHeader (ML,
-- FUAM, DCM, NSF), NSF standard features, NVF (FeatureCount), NVF vendor
-- features, and nothing after them (rreq.extent). A feature's mask is ML
-- bytes: the walker hands each feature exactly its code and ML bytes, and
-- the mask, `size deduced`, must be 1, 2, 4 or 8 bytes. The features are
-- copies of jp2-boxes.asn1's StandardFeature and VendorFeature, whose masks
-- take ML as an ACN parameter.
RreqHeader ::= SEQUENCE {
    fuam        RreqMask,
    dcm         RreqMask,
    nsf         FeatureCount
}

RreqStandardFeature ::= SEQUENCE {
    sf          FeatureCode,
    sm          RreqMask
}

RreqVendorFeature ::= SEQUENCE {
    vf          VendorId,
    vm          RreqMask
}

-- NSF and NVF.
FeatureCount ::= INTEGER (0..65535)

-- An entry of a Number List box (M.11.12, Table M.42), which the whole-file
-- model keeps opaque: AN, the type of entity in its high byte (0 the
-- rendered result, whose number is 0; 1 a codestream, 2 a compositing
-- layer) and the entity's number in the three low bytes. For hv_merge,
-- which writes one.
NlstEntry ::= SEQUENCE {
    entity      INTEGER (0..2),
    number      INTEGER (0..16777215)
} (WITH COMPONENTS {entity (0), number (0)} | WITH COMPONENTS {..., entity (1..2)})

-- Palette box (T.800 I.5.3.4), one part at a time: PclrCounts (NE, NPC),
-- NPC BitDepths (jp2-boxes.asn1), then the entries, whose length is a rule
-- (pclr.entries-length). PclrCounts is the head of jp2-boxes.asn1's
-- PclrHeader, where NPC is the depths' count, an ACN determinant.
PclrCounts ::= SEQUENCE {
    ne          INTEGER (1..1024),
    npc         INTEGER (1..255)
}

-- SOT marker segment after the FF90 code, A.4.2 (Table A.5). The
-- whole-file model's TilePart has Psot as a determinant instead.
SotSegment ::= SEQUENCE {
    lsot        INTEGER (10..10),
    isot        INTEGER (0..65534),               -- tile index
    psot        INTEGER (0 | 14..4294967295),     -- tile-part length from the SOT code;
                                                  -- 0: runs to the EOC (last tile-part only).
                                                  -- 14 = SOT segment 12 + SOD 2
    tpsot       INTEGER (0..254),                 -- tile-part index (255 reserved)
    tnsot       INTEGER (0..255)                  -- number of tile-parts; 0 = not specified
}

END

-- ===========================================================================
-- Rules the walker applies (ASN.1 cannot state them per type)
-- ===========================================================================
--
-- BoxHeader:
--   payload = lbox - 8 when lbox >= 8, xlbox - 16 when lbox = 1, and the rest
--     of the file when lbox = 0; the box must fit inside its parent.
--   lbox = 0 only for the last box of the file (I.4).
-- SotSegment:
--   the tile-part runs psot bytes from the SOT code, or up to the EOC that
--     ends the codestream when psot = 0; psot = 0 only on the last tile-part
--     (A.4.2).
--   The tile-part rules of j2k-codestream.asn1 (tpsot order, tnsot, COD/QCD
--     placement) apply unchanged.
